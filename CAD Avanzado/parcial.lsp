(defun C:Parcial()
  (setq puntoInsercion (getpoint "\nSeleccione el punto de insercion: ")
	largoMango (getreal "\nIngrese el largo del mango: ")
	longitudVastago (* 0.8 largoMango)
	diametroVastago (* 0.05 largoMango)
	diametroMango (* 0.07 largoMango)
	longitudPunta (* 0.1 largoMango)
	diametroEntalladura (* 0.15 diametroMango)
	var (getvar "osmode")
	insercionVastago (list (car puntoInsercion) 
			       (car (cdr puntoInsercion))
			       (+ (car (cdr (cdr puntoInsercion))) largoMango))
	punta (list (+ (car puntoInsercion) (/ diametroVastago 2))
		    (car (cdr puntoInsercion))
		    (+ (car (cdr (cdr insercionVastago))) longitudVastago))
	entalladura (list (+ (car puntoInsercion) (/ diametroMango 2))
			  (car (cdr puntoInsercion))
			  (car (cdr (cdr puntoInsercion))))
	union (list (+ (car puntoInsercion) (/ diametroVastago) 2)
		    (car (cdr puntoInsercion))
		    (car (cdr (cdr insercionVastago))))
  )
  (setvar "osmode" 0)
  (command "CYLINDER" entalladura "d" diametroEntalladura largoMango)
  (setq entAux (entlast))
  (command "ARRAY" entAux "" "p" puntoInsercion 10 "" "")
  (command "UNION" "all" "")
  (setq cilindros (entlast))
  (command "CYLINDER" puntoInsercion "d" diametroMango largoMango)
  (setq mango (entlast))
  (command "CYLINDER" insercionVastago "d" diametroVastago longitudVastago)
  (setq vastago (entlast))
  (command "UNION" mango vastago "")
  (setq punzon (entlast))
  (command "FILLET" entalladura (/ diametroMango 2) entalladura "")
  (setq punzon (entlast))
  (command "CHAMFER" punta "" (/ diametroVastago 2) longitudPunta punta "")
  (setq punzon (entlast))
  (command "FILLET" union (/ (- diametroMango diametroVastago) 2) union "")
  (setq punzon (entlast))
  (command "SUBTRACT" punzon "" cilindros "")
  (PRINC)
)
